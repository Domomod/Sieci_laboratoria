IANAifType-MIB DEFINITIONS ::= BEGIN

   IMPORTS
       MODULE-IDENTITY, mib-2      FROM SNMPv2-SMI
       TEXTUAL-CONVENTION          FROM SNMPv2-TC;

    -- I am removing the {} specifiers, they were to long to store in a regexp string 
    IANAifType ::= INTEGER 

    IANAtunnelType ::= INTEGER

   END
